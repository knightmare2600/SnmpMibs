TPLINK-PORTSECURITY-MIB DEFINITIONS ::= BEGIN
		IMPORTS
		  OBJECT-TYPE,MODULE-IDENTITY,
		  NOTIFICATION-TYPE
			  	         	FROM SNMPv2-SMI
			ifIndex						
										FROM RFC1213-MIB
			DisplayString 
										FROM SNMPv2-TC 								
			tplinkMgmt

										FROM TPLINK-MIB;

   		tplinkPortSecurityMIB MODULE-IDENTITY  
	    LAST-UPDATED    "201212130000Z"
	    ORGANIZATION    "TPLINK"
	    CONTACT-INFO		"www.tplink.com.cn"
	    DESCRIPTION			"The config of the port security."
	    REVISION        "201212130000Z"
	    DESCRIPTION			"Initial version of this MIB module."
	    ::= { tplinkMgmt 12 } 
			

		tplinkPortSecurityMIBObjects		OBJECT IDENTIFIER	::= { tplinkPortSecurityMIB 1 }
		tplinkPortSecurityNotifications		OBJECT IDENTIFIER	::= { tplinkPortSecurityMIB 2 }
		
		
  		tpPortSecurityTable	OBJECT-TYPE
  			SYNTAX			SEQUENCE OF TpPortSecurityEntry
  			MAX-ACCESS 	not-accessible
  			STATUS 			current
  			DESCRIPTION 
  			"A table that contains security information about every port.
  			Port Security is to protect the switch from the malicious MAC 
  			address attack by limiting the maximum number of MAC addresses
  			that can be learned on the port. The port with Port Security 
  			feature enabled will learn the MAC address dynamically. When
  			the learned MAC address number reaches the maximum, the port
  			will stop learning. Thereafter, the other devices with the MAC
  			address unlearned can not access to the network via this port."
  			::= {tplinkPortSecurityMIBObjects 1}
  			
  		tpPortSecurityEntry OBJECT-TYPE
  			SYNTAX			TpPortSecurityEntry
  			MAX-ACCESS	not-accessible
  			STATUS			current
  			DESCRIPTION	
  			"A list security information for each port of the device."
  			INDEX{ifIndex}
  			::= {tpPortSecurityTable 1}
  			
  		TpPortSecurityEntry	::=
  		SEQUENCE
  		{
  			tpPortSecurityPortIndex
  				DisplayString,
  			tpPortSecurityMaxNum
  				INTEGER,
  			tpPortSecurityLearnNum
  				INTEGER,
  			tpPortSecurityLearnMode
  				INTEGER,
  			tpPortSecurityPortStatus
  				INTEGER
  		}
  		
  		tpPortSecurityPortIndex OBJECT-TYPE
  			SYNTAX			DisplayString(SIZE(0..16))
  			MAX-ACCESS	read-only
  			STATUS			current
  			DESCRIPTION	
  			"This object indicates the port number."
  			::= {tpPortSecurityEntry 1}
  			
  		tpPortSecurityMaxNum OBJECT-TYPE
  			SYNTAX			INTEGER(0..1024)
  			MAX-ACCESS	read-write
  			STATUS			current
  			DESCRIPTION	
  			"This object indicates the maximum number of MAC addresses that
  			can be learned on the port."
  			::= {tpPortSecurityEntry 2}
  			
  		tpPortSecurityLearnNum OBJECT-TYPE
  			SYNTAX			INTEGER
  			MAX-ACCESS	read-only
  			STATUS			current
  			DESCRIPTION	
  			"This object indicates the number of MAC addresses that have been
  			learned on the port."
  			::= {tpPortSecurityEntry 3}
  		
  		tpPortSecurityLearnMode	OBJECT-TYPE
  			SYNTAX			
  				INTEGER
  				{
  					dynamic(0),
  					static(1),
  					permanent(2)
  				}
  			MAX-ACCESS	read-write
  			STATUS			current
  			DESCRIPTION	
  			"This object indicates the learn mode of the port.
  			
  			dynamic: When dynamic mode is selected, the learned MAC address
  			will be deleted automatically after the aging time.
  			
  			static: When static mode is selected, the learned MAC address will
  			be out of the influence of the aging time and can only be deleted 
  			manually. The learned entries will be cleared after the switch is 
  			rebooted.
  			
  			permanent: When permanent mode is selected, the learned MAC address 
  			will be out of the influence of the aging time and can only be 
  			deleted manually. The learned entries will be saved even the switch
  			is rebooted. "
  			
  			::= {tpPortSecurityEntry 4}
  			
  		tpPortSecurityPortStatus OBJECT-TYPE
  			SYNTAX			
  			INTEGER
  			{
  				disable(0),
  				enable(1)
  			}
  			MAX-ACCESS	read-write
  			STATUS			current
  			DESCRIPTION	
  			"This object indicates the security feature of the port."
  			::= {tpPortSecurityEntry 5}						          	  	          
END
