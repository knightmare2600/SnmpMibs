TPLINK-DHCPSERVER-MIB DEFINITIONS ::= BEGIN

IMPORTS
    MODULE-IDENTITY,
    OBJECT-TYPE,
    IpAddress
			FROM SNMPv2-SMI 
	tplinkMgmt	          
			FROM TPLINK-MIB           
	TPRowStatus       	 
			FROM TPLINK-TC-MIB;

tplinkDhcpServerMIB MODULE-IDENTITY
    LAST-UPDATED  "201211290000Z"
    ORGANIZATION  "TP-LINK"
    CONTACT-INFO  "www.tplink.com.cn"
    DESCRIPTION
         "This MIB module contain a collection of managed objects
          that apply to network devices with Dhcp Server function."
    REVISION    "201211290000Z"
    DESCRIPTION
        "Initial version of this MIB module."
    ::= { tplinkMgmt 38 }

tplinkDhcpServerMIBObjects OBJECT IDENTIFIER ::= {tplinkDhcpServerMIB 1}
tplinkDhcpServerNotifications OBJECT IDENTIFIER ::= {tplinkDhcpServerMIB 2}

-- Global configuration of Dhcp Server

tpDhcpServerEnable OBJECT-TYPE
	SYNTAX  INTEGER{
		disable(0), 						--disable
		enable(1)							--enable
	}
	MAX-ACCESS  read-write
	STATUS  current
	DESCRIPTION
		"Select Enable/Disable DHCP server function globally on the Switch."
	::= { tplinkDhcpServerMIBObjects 1 }
              
              
tpDhcpServerUnusedIpTable OBJECT-TYPE
	SYNTAX  SEQUENCE OF TpDhcpServerUnusedIpEntry
	MAX-ACCESS not-accessible
	STATUS  current
	DESCRIPTION
		"A list of distributed IP entries by the DHCP server."
	::= {tplinkDhcpServerMIBObjects 2}  
     
tpDhcpServerUnusedIpEntry OBJECT-TYPE
	SYNTAX  TpDhcpServerUnusedIpEntry
	MAX-ACCESS  not-accessible
	STATUS  current
	DESCRIPTION
		" A group of IP entries."
	INDEX   { tpDhcpServerUnusedStartIp}
	::= { tpDhcpServerUnusedIpTable 1 }   
				     
TpDhcpServerUnusedIpEntry ::=
	SEQUENCE {
		tpDhcpServerUnusedStartIp
			IpAddress, 
		tpDhcpServerUnusedEndIp
			IpAddress,
		tpDhcpServerUnusedIpStatus
			TPRowStatus
	}
              
tpDhcpServerUnusedStartIp OBJECT-TYPE
	SYNTAX  IpAddress
	MAX-ACCESS  read-only
	STATUS  current
	DESCRIPTION
		"Every DHCP Server own a lot of ip address ,here is the start unused ip address."
	::= { tpDhcpServerUnusedIpEntry 1 }
              
tpDhcpServerUnusedEndIp OBJECT-TYPE
	SYNTAX  IpAddress
	MAX-ACCESS  read-create
	STATUS  current
	DESCRIPTION
		"The end unused ip address of the DHCP server."
	::= { tpDhcpServerUnusedIpEntry 2 }
tpDhcpServerUnusedIpStatus OBJECT-TYPE
	SYNTAX  TPRowStatus
	MAX-ACCESS  read-create
	STATUS  current
	DESCRIPTION
		" The following values are states:
		these values may be used as follow:
		active(1),if the entry is being used.
		createAndGo(4),not being used.
		destroy(6),destory the entry."
	::={ tpDhcpServerUnusedIpEntry 3 }


-- Dhcp Server Address Table

tpDhcpServerAddrPoolTable OBJECT-TYPE
	SYNTAX  SEQUENCE OF TpDhcpServerAddrPoolEntry
	MAX-ACCESS not-accessible
	STATUS  current
	DESCRIPTION
		"A list of entries in DHCP server address pool."
	::= {tplinkDhcpServerMIBObjects 3}  	      
       
tpDhcpServerAddrPoolEntry OBJECT-TYPE
	SYNTAX  TpDhcpServerAddrPoolEntry
	MAX-ACCESS  not-accessible
	STATUS  current
	DESCRIPTION
		" A group of IP entries."
	INDEX   { tpDhcpServerAddrPoolNetwork }
	::= { tpDhcpServerAddrPoolTable 1 }   
				     
TpDhcpServerAddrPoolEntry ::=
	SEQUENCE {
		tpDhcpServerAddrPoolName
			OCTET STRING, 
		tpDhcpServerAddrPoolNetwork
			IpAddress, 
		tpDhcpServerAddrPoolSubnetMask
			IpAddress,
		tpDhcpServerAddrPoolRentTime
			INTEGER,
		tpDhcpServerAddrPoolGateWayA
			IpAddress,
		tpDhcpServerAddrPoolGateWayB
			IpAddress,
		tpDhcpServerAddrPoolGateWayC
			IpAddress,
		tpDhcpServerAddrPoolGateWayD
			IpAddress,
		tpDhcpServerAddrPoolGateWayE
			IpAddress,
		tpDhcpServerAddrPoolGateWayF
			IpAddress,
		tpDhcpServerAddrPoolGateWayG
 			IpAddress,
		tpDhcpServerAddrPoolGateWayH
			IpAddress,
		tpDhcpServerAddrPoolDnsA
			IpAddress,
		tpDhcpServerAddrPoolDnsB
			IpAddress,
		tpDhcpServerAddrPoolDnsC
			IpAddress,
		tpDhcpServerAddrPoolDnsD
			IpAddress,
		tpDhcpServerAddrPoolDnsE
			IpAddress,
		tpDhcpServerAddrPoolDnsF
			IpAddress,
		tpDhcpServerAddrPoolDnsG
			IpAddress,
		tpDhcpServerAddrPoolDnsH
			IpAddress,
		tpDhcpServerAddrPoolStatus
			TPRowStatus
	}
              
tpDhcpServerAddrPoolName OBJECT-TYPE
	SYNTAX  OCTET STRING (SIZE (0..8)) 
	MAX-ACCESS  read-create
	STATUS  current
	DESCRIPTION
		"The entry name."
	::= { tpDhcpServerAddrPoolEntry 1 }
              
tpDhcpServerAddrPoolNetwork OBJECT-TYPE
	SYNTAX  IpAddress  
	MAX-ACCESS  read-create
	STATUS  current
	DESCRIPTION
		"The address of network."
	::= { tpDhcpServerAddrPoolEntry 2 }
    
tpDhcpServerAddrPoolSubnetMask OBJECT-TYPE
	SYNTAX  IpAddress  
	MAX-ACCESS  read-create
	STATUS  current
	DESCRIPTION
		"The address of subnet mask."
	::= { tpDhcpServerAddrPoolEntry 3 }
              
tpDhcpServerAddrPoolRentTime OBJECT-TYPE
	SYNTAX  INTEGER 
	MAX-ACCESS  read-create
	STATUS  current
	DESCRIPTION
		"The rent time."
	::= { tpDhcpServerAddrPoolEntry 4 } 
              
tpDhcpServerAddrPoolGateWayA OBJECT-TYPE
	SYNTAX  IpAddress  
	MAX-ACCESS  read-create
	STATUS  current
	DESCRIPTION
		"The address of gateway."
	::= { tpDhcpServerAddrPoolEntry 5 }
              
tpDhcpServerAddrPoolGateWayB OBJECT-TYPE
	SYNTAX  IpAddress  
	MAX-ACCESS  read-create
	STATUS  current
	DESCRIPTION
		"The address of gateway."
	::= { tpDhcpServerAddrPoolEntry 6 }          
tpDhcpServerAddrPoolGateWayC OBJECT-TYPE
	SYNTAX  IpAddress  
	MAX-ACCESS  read-create
	STATUS  current
	DESCRIPTION
		"The address of gateway."
	::= { tpDhcpServerAddrPoolEntry 7 }         
tpDhcpServerAddrPoolGateWayD OBJECT-TYPE
	SYNTAX  IpAddress  
	MAX-ACCESS  read-create
	STATUS  current
	DESCRIPTION
		"The address of gateway."
	::= { tpDhcpServerAddrPoolEntry 8 }      
tpDhcpServerAddrPoolGateWayE OBJECT-TYPE
	SYNTAX  IpAddress  
	MAX-ACCESS  read-create
	STATUS  current
	DESCRIPTION
		"The address of gateway."
	::= { tpDhcpServerAddrPoolEntry 9 }
tpDhcpServerAddrPoolGateWayF OBJECT-TYPE
	SYNTAX  IpAddress  
	MAX-ACCESS  read-create
	STATUS  current
	DESCRIPTION
		"The address of gateway."
	::= { tpDhcpServerAddrPoolEntry 10 } 
              
tpDhcpServerAddrPoolGateWayG OBJECT-TYPE
	SYNTAX  IpAddress  
	MAX-ACCESS  read-create
	STATUS  current
	DESCRIPTION
		"The address of gateway."
	::= { tpDhcpServerAddrPoolEntry 11 }  
tpDhcpServerAddrPoolGateWayH OBJECT-TYPE
	SYNTAX  IpAddress  
	MAX-ACCESS  read-create
	STATUS  current
	DESCRIPTION
		"The address of gateway."
	::= { tpDhcpServerAddrPoolEntry 12 }               
    
tpDhcpServerAddrPoolDnsA OBJECT-TYPE
	SYNTAX  IpAddress  
	MAX-ACCESS  read-create
	STATUS  current
	DESCRIPTION
		"The address of dns."
	::= { tpDhcpServerAddrPoolEntry 13 }
              
tpDhcpServerAddrPoolDnsB OBJECT-TYPE
	SYNTAX  IpAddress  
	MAX-ACCESS  read-create
	STATUS  current
	DESCRIPTION
		"The address of dns."
	::= { tpDhcpServerAddrPoolEntry 14 }          
tpDhcpServerAddrPoolDnsC OBJECT-TYPE
	SYNTAX  IpAddress  
	MAX-ACCESS  read-create
	STATUS  current
	DESCRIPTION
		"The address of dns."
	::= { tpDhcpServerAddrPoolEntry 15 }         
tpDhcpServerAddrPoolDnsD OBJECT-TYPE
	SYNTAX  IpAddress  
	MAX-ACCESS  read-create
	STATUS  current
	DESCRIPTION
		"The address of dns."
	::= { tpDhcpServerAddrPoolEntry 16 }      
tpDhcpServerAddrPoolDnsE OBJECT-TYPE
	SYNTAX  IpAddress  
	MAX-ACCESS  read-create
	STATUS  current
	DESCRIPTION
		"The address of dns."
	::= { tpDhcpServerAddrPoolEntry 17 }
tpDhcpServerAddrPoolDnsF OBJECT-TYPE
	SYNTAX  IpAddress  
	MAX-ACCESS  read-create
	STATUS  current
	DESCRIPTION
		"The address of dns."
	::= { tpDhcpServerAddrPoolEntry 18 } 
              
tpDhcpServerAddrPoolDnsG OBJECT-TYPE
	SYNTAX  IpAddress  
	MAX-ACCESS  read-create
	STATUS  current
	DESCRIPTION
		"The address of dns."
	::= { tpDhcpServerAddrPoolEntry 19 }  
tpDhcpServerAddrPoolDnsH OBJECT-TYPE
	SYNTAX  IpAddress  
	MAX-ACCESS  read-create
	STATUS  current
	DESCRIPTION
		"The address of dns."
	::= { tpDhcpServerAddrPoolEntry 20 } 
tpDhcpServerAddrPoolStatus OBJECT-TYPE
	SYNTAX  TPRowStatus
	MAX-ACCESS  read-create
	STATUS  current
	DESCRIPTION
		" The following values are states:
		these values may be used as follow:
		active(1),if the entry is being used.
		createAndGo(4),not being used.
		destroy(6),destory the entry."
         	::={ tpDhcpServerAddrPoolEntry 21 }
         	
--  Dhcp Server manual binding table

tpDhcpServerStaticBindTable OBJECT-TYPE
	SYNTAX  SEQUENCE OF TPDHCPSERVERSTATICBINDENTRY
	MAX-ACCESS not-accessible
	STATUS  current
	DESCRIPTION
		"A list of entries in DHCP server static bind table."
	::= {tplinkDhcpServerMIBObjects 4}  	      
       
tpDhcpServerStaticBindEntry OBJECT-TYPE
	SYNTAX  TPDHCPSERVERSTATICBINDENTRY
	MAX-ACCESS  not-accessible
	STATUS  current
	DESCRIPTION
		" A group of IP entries."
	INDEX   { tpDhcpServerBindIpAddr }
	::= { tpDhcpServerStaticBindTable 1 }   
				     
TPDHCPSERVERSTATICBINDENTRY ::=
	SEQUENCE {
		tpDhcpServerStaticAddrPoolName
			OCTET STRING, 
		tpDhcpServerBindIpAddr
			IpAddress,
		tpDhcpServerStaticClientId
			OCTET STRING, 
		tpDhcpServerMacAddr
			OCTET STRING,		
		tpDhcpServerHardwareType
			INTEGER,
		tpDhcpServerStaticBindStatus
			TPRowStatus
	}
              
tpDhcpServerStaticAddrPoolName OBJECT-TYPE
	SYNTAX  OCTET STRING (SIZE (0..8)) 
	MAX-ACCESS  read-create
	STATUS  current
	DESCRIPTION
		"The entry name."
	::= { tpDhcpServerStaticBindEntry 1 }

tpDhcpServerBindIpAddr OBJECT-TYPE
	SYNTAX  IpAddress  
	MAX-ACCESS  read-create
	STATUS  current
	DESCRIPTION
		"The static binding ip address."
	::= { tpDhcpServerStaticBindEntry 2 }
	
tpDhcpServerStaticClientId OBJECT-TYPE
	SYNTAX  OCTET STRING (SIZE (0..16))
	MAX-ACCESS  read-create
	STATUS  current
	DESCRIPTION
		"The identifier of the client."
	::= { tpDhcpServerStaticBindEntry 3 }

tpDhcpServerMacAddr OBJECT-TYPE
	SYNTAX  OCTET STRING (SIZE (0..255))
	MAX-ACCESS  read-create
	STATUS  current
	DESCRIPTION
		"The mac address of network."
	::= { tpDhcpServerStaticBindEntry 4 }                                         
              
tpDhcpServerHardwareType OBJECT-TYPE
	SYNTAX  INTEGER (0..6)
	MAX-ACCESS  read-create
	STATUS  current
	DESCRIPTION
		"The hardware type. 0 stands for not using mac but client identifier to bind."
	::= { tpDhcpServerStaticBindEntry 5 }   	
tpDhcpServerStaticBindStatus OBJECT-TYPE
	SYNTAX  TPRowStatus
	MAX-ACCESS  read-create
	STATUS  current
	DESCRIPTION
		" The following values are states:
		these values may be used as follow:
		active(1),if the entry is being used.
		createAndGo(4),not being used.
		destroy(6),destory the entry."
	::={ tpDhcpServerStaticBindEntry 6 } 

-- Dhcp Server Bindings
tpDhcpServerBindingTable OBJECT-TYPE
	SYNTAX  SEQUENCE OF TPDHCPSERVERBINDINGENTRY
	MAX-ACCESS not-accessible
	STATUS  current
	DESCRIPTION
		"A list of entries in DHCP server bindings."
	::= {tplinkDhcpServerMIBObjects 5}  	      
       
tpDhcpServerBindingEntry OBJECT-TYPE
	SYNTAX  TPDHCPSERVERBINDINGENTRY
	MAX-ACCESS  not-accessible
	STATUS  current
	DESCRIPTION
		" A group of IP entries."
	INDEX   {tpDhcpServerBindingIp}
	::= { tpDhcpServerBindingTable 1 }   

TPDHCPSERVERBINDINGENTRY ::=
	SEQUENCE { 
		tpDhcpServerBindingIp
			IpAddress,
		tpDhcpServerBindingClientId
			OCTET STRING,
		tpDhcpServerBindingMac
			OCTET STRING,
		tpDhcpServerBindingType
			INTEGER,
		tpDhcpServerBindingRemainTime
			OCTET STRING,
		tpDhcpServerBindingStatus
			TPRowStatus
	}

tpDhcpServerBindingIp OBJECT-TYPE
	SYNTAX  IpAddress  
	MAX-ACCESS  read-only
	STATUS  current
	DESCRIPTION
		"The address of subnet mask."
	::= { tpDhcpServerBindingEntry 1 }
                                        
tpDhcpServerBindingClientId OBJECT-TYPE
	SYNTAX  OCTET STRING (SIZE (0..200)) 
	MAX-ACCESS  read-only
	STATUS  current
	DESCRIPTION
		"The identifier of the client."
	::= { tpDhcpServerBindingEntry 2 }

tpDhcpServerBindingMac OBJECT-TYPE
	SYNTAX  OCTET STRING (SIZE (0..255)) 
	MAX-ACCESS  read-only
	STATUS  current
	DESCRIPTION
		"The address of network."
	::= { tpDhcpServerBindingEntry 3 }
    
tpDhcpServerBindingType OBJECT-TYPE
	SYNTAX  INTEGER{
		automatic(0), 						--automatic
		manual(1)							--manual
	}
	MAX-ACCESS  read-only
	STATUS  current
	DESCRIPTION
		"The binding type."
	::= { tpDhcpServerBindingEntry 4 }                                    

tpDhcpServerBindingRemainTime OBJECT-TYPE
	SYNTAX  OCTET STRING (SIZE (0..16)) 
	MAX-ACCESS  read-only
	STATUS  current
	DESCRIPTION
		"The rent time."
	::= { tpDhcpServerBindingEntry 5 }   	
	
tpDhcpServerBindingStatus OBJECT-TYPE
	SYNTAX  TPRowStatus
	MAX-ACCESS  read-create
	STATUS  current
	DESCRIPTION
			 " The following values are states:
			 these values may be used as follow:
			 active(1),if the entry is being used.
			 createAndGo(4),not being used.
			 destroy(6),destory the entry."
	::= { tpDhcpServerBindingEntry 6 }   	
	
tpDhcpServerBindingClear	OBJECT-TYPE
	SYNTAX  INTEGER{
		remain(0), 						--remain
		clear(1)						--clear
	}
	MAX-ACCESS  read-write
	STATUS  current
	DESCRIPTION
		"Clear the DHCP bindings."
	::= { tplinkDhcpServerMIBObjects 7 }
	
-- Dhcp Server Statistics
tpDhcpServerStatistics OBJECT IDENTIFIER ::= {tplinkDhcpServerMIBObjects 8}

tpDhcpServerStatisticsBootRequest OBJECT-TYPE
    SYNTAX INTEGER
	MAX-ACCESS read-only
	STATUS  current
	DESCRIPTION
		"Displays the Bootp Request packets received."
	::= {tpDhcpServerStatistics 1}
	
tpDhcpServerStatisticsDiscover OBJECT-TYPE
    SYNTAX INTEGER
	MAX-ACCESS read-only
	STATUS  current
	DESCRIPTION
		"Displays the Discover packets received."
	::= {tpDhcpServerStatistics 2}

tpDhcpServerStatisticsRequest OBJECT-TYPE
    SYNTAX INTEGER
	MAX-ACCESS read-only
	STATUS  current
	DESCRIPTION
		"Displays the Request packets received."
	::= {tpDhcpServerStatistics 3}
	
tpDhcpServerStatisticsDecline OBJECT-TYPE
    SYNTAX INTEGER
	MAX-ACCESS read-only
	STATUS  current
	DESCRIPTION
		"Displays the Decline packets received."
	::= {tpDhcpServerStatistics 4}
	
tpDhcpServerStatisticsRelease OBJECT-TYPE
    SYNTAX INTEGER
	MAX-ACCESS read-only
	STATUS  current
	DESCRIPTION
		"Displays the Release packets received."
	::= {tpDhcpServerStatistics 5}
	
tpDhcpServerStatisticsInform OBJECT-TYPE
    SYNTAX INTEGER
	MAX-ACCESS read-only
	STATUS  current
	DESCRIPTION
		"Displays the Inform packets received."
	::= {tpDhcpServerStatistics 6}
	
tpDhcpServerStatisticsBootReply OBJECT-TYPE
    SYNTAX INTEGER
	MAX-ACCESS read-only
	STATUS  current
	DESCRIPTION
		"Displays the Bootp reply packets sent."
	::= {tpDhcpServerStatistics 7}
	
tpDhcpServerStatisticsOffer OBJECT-TYPE
    SYNTAX INTEGER
	MAX-ACCESS read-only
	STATUS  current
	DESCRIPTION
		"Displays the Offer packets sent."
	::= {tpDhcpServerStatistics 8}
	
tpDhcpServerStatisticsAck OBJECT-TYPE
    SYNTAX INTEGER
	MAX-ACCESS read-only
	STATUS  current
	DESCRIPTION
		"Displays the Ack packets sent."
	::= {tpDhcpServerStatistics 9}
	
tpDhcpServerStatisticsNak OBJECT-TYPE
    SYNTAX INTEGER
	MAX-ACCESS read-only
	STATUS  current
	DESCRIPTION
		"Displays the Nak packets sent."
	::= {tpDhcpServerStatistics 10}
	
tpDhcpServerStatisticsClear OBJECT-TYPE
    SYNTAX INTEGER{
		remain(0), 						--remain
		clear(1)						--clear
	}
	MAX-ACCESS read-write
	STATUS  current
	DESCRIPTION
		"Clear the packet statistics."
	::= {tpDhcpServerStatistics 11}
       
tpDhcpServerPingPackets	OBJECT-TYPE
	SYNTAX  INTEGER (0..10)
	MAX-ACCESS  read-write
	STATUS  current
	DESCRIPTION
		"The number of packets to be sent."
	::= { tplinkDhcpServerMIBObjects 9 }

tpDhcpServerPingTimeout	OBJECT-TYPE
	SYNTAX  INTEGER (100..10000)
	MAX-ACCESS  read-write
	STATUS  current
	DESCRIPTION
		"The time it takes to determine the specific IP not exist."
	::= { tplinkDhcpServerMIBObjects 10 }

END
