TPLINK-USERSECURITY-MIB DEFINITIONS ::= BEGIN

          IMPORTS
			  TPRowStatus       	 
  					FROM TPLINK-TC-MIB
              OBJECT-TYPE,MODULE-IDENTITY,IpAddress
          	  	         	FROM SNMPv2-SMI
              tplinkMgmt	          
          	  	          FROM TPLINK-MIB
			  ifIndex 
							FROM  RFC1213-MIB;
  	  	
  	  	MacAddress ::= OCTET STRING (SIZE (6))          	
  	  	
	      tplinkUserSecurity MODULE-IDENTITY  
		    LAST-UPDATED    "2009070900Z"
		    ORGANIZATION    "TPLINK"
		    CONTACT-INFO    "www.tplink.com.cn"
		    DESCRIPTION
		             "Implementation of the user security is mandatory for the
					swtich."
		    REVISION        "2009070900Z"
		    DESCRIPTION
				"Initial version of this MIB module."
		    ::= { tplinkMgmt 41 }      	               
          
		   tplinkUserSecurityMIBObjects   OBJECT IDENTIFIER    ::=  {tplinkUserSecurity 1}
		   tplinkUserSecurityMIBNotifications OBJECT IDENTIFIER ::=   {tplinkUserSecurity 2}
          userSecurityUserAuth OBJECT IDENTIFIER ::= { tplinkUserSecurityMIBObjects 1}   
          
          userSecurityUserAuthType OBJECT-TYPE
              SYNTAX INTEGER{
	      		disable(0), 					
	      		ip(1),
	      		mac(2),
	      		port(3)					
	      	   }
              MAX-ACCESS  read-only
              STATUS  current
              DESCRIPTION
                      "disable(0), 					
	      		ip(1),
	      		mac(2),
	      		port(3)
	      		The mode of user authentication."
              ::= { userSecurityUserAuth 1 }
          
         userSecurityUserAuthPort OBJECT IDENTIFIER ::= { userSecurityUserAuth 2 }
         
         userSecurityUserAuthPortEnable OBJECT-TYPE
              SYNTAX  INTEGER{
	      		disable(0), 					
	      		enable(1)					
	      		}
              MAX-ACCESS  read-write
              STATUS  current
              DESCRIPTION
                       "0. disable
                      1.enable"
              ::= { userSecurityUserAuthPort 1 }
			  
		  userSecurityUserAuthPortAccessSnmp OBJECT-TYPE
              SYNTAX  INTEGER{
	      		disable(0), 					
	      		enable(1)					
	      		}
              MAX-ACCESS  read-write
              STATUS  current
              DESCRIPTION
                      "0. disable -- SNMP frame sent to the switch through the port will be dropped
					  1. enable -- SNMP frame sent to the switch through the port will be accepted"
              ::= { userSecurityUserAuthPort 2 }
			  
			userSecurityUserAuthPortAccessTelnet OBJECT-TYPE
              SYNTAX  INTEGER{
	      		disable(0), 					
	      		enable(1)					
	      		}
              MAX-ACCESS  read-write
              STATUS  current
              DESCRIPTION
                      "0. disable -- Telnet frame sent to the switch through the port will be dropped
					  1. enable -- Telnet frame sent to the switch through the port will be accepted"
              ::= { userSecurityUserAuthPort 3 }
			  
			userSecurityUserAuthPortAccessSsh OBJECT-TYPE
              SYNTAX  INTEGER{
	      		disable(0), 					
	      		enable(1)					
	      		}
              MAX-ACCESS  read-write
              STATUS  current
              DESCRIPTION
                      "0. disable -- SSH frame sent to the switch through the port will be dropped
					  1. enable -- SSH frame sent to the switch through the port will be accepted"
              ::= { userSecurityUserAuthPort 4 }
			  
			userSecurityUserAuthPortAccessHttp OBJECT-TYPE
              SYNTAX  INTEGER{
	      		disable(0), 					
	      		enable(1)					
	      		}
              MAX-ACCESS  read-write
              STATUS  current
              DESCRIPTION
                      "0. disable -- HTTP frame sent to the switch through the port will be dropped
					  1. enable -- HTTP frame sent to the switch through the port will be accepted"
              ::= { userSecurityUserAuthPort 5 }
			  
			userSecurityUserAuthPortAccessHttps OBJECT-TYPE
              SYNTAX  INTEGER{
	      		disable(0), 					
	      		enable(1)					
	      		}
              MAX-ACCESS  read-write
              STATUS  current
              DESCRIPTION
                      "0. disable -- HTTPS frame sent to the switch through the port will be dropped
					  1. enable -- HTTPS frame sent to the switch through the port will be accepted"
              ::= { userSecurityUserAuthPort 6 }
			  
			userSecurityUserAuthPortAccessPing OBJECT-TYPE
              SYNTAX  INTEGER{
	      		disable(0), 					
	      		enable(1)					
	      		}
              MAX-ACCESS  read-write
              STATUS  current
              DESCRIPTION
                      "0. disable -- Ping request frame sent to the switch through the port will be dropped
					  1. enable -- Ping request frame sent to the switch through the port will be accepted"
              ::= { userSecurityUserAuthPort 7 }
              
         
          userSecurityUserAuthPortTable OBJECT-TYPE
              SYNTAX  SEQUENCE OF USERSECURITYUSERAUTHPORTENTRY
              MAX-ACCESS  not-accessible
              STATUS  current
              DESCRIPTION
                      "A list of port."
              ::= { userSecurityUserAuthPort 8 }
          
          userSecurityUserAuthPortEntry OBJECT-TYPE
              SYNTAX  USERSECURITYUSERAUTHPORTENTRY
              MAX-ACCESS  not-accessible
              STATUS  current
              DESCRIPTION
                      "An entry contains of the port for user auth ."
              INDEX   { ifIndex }
              ::= { userSecurityUserAuthPortTable 1 }
              
              
          USERSECURITYUSERAUTHPORTENTRY ::=
           SEQUENCE {
                  userSecurityUserAuthPortConf
                      INTEGER
          }
        
            userSecurityUserAuthPortConf OBJECT-TYPE
              SYNTAX  INTEGER{
	      		disable(0), 					
	      		enable(1)					
	      		}
              MAX-ACCESS  read-write
              STATUS  current
              DESCRIPTION
                      "0. disable
                      1.enable"
              ::= { userSecurityUserAuthPortEntry 2 }
              
          --IP     
          userSecurityUserAuthIp  OBJECT IDENTIFIER ::= { userSecurityUserAuth 3 }
          
          userSecurityUserAuthIpEnable OBJECT-TYPE
              SYNTAX  INTEGER{
	      		disable(0), 					
	      		enable(1)					
	      		}
              MAX-ACCESS  read-write
              STATUS  current
              DESCRIPTION
                       "0. disable
                      1.enable"
              ::= { userSecurityUserAuthIp 1 }   
		
		  userSecurityUserAuthIpAccessSnmp OBJECT-TYPE
              SYNTAX  INTEGER{
	      		disable(0), 					
	      		enable(1)					
	      		}
              MAX-ACCESS  read-write
              STATUS  current
              DESCRIPTION
                      "0. disable -- SNMP frame sent to the switch will be dropped
					  1. enable -- SNMP frame whose source ip is auth ip sent to the switch will be accepted"
              ::= { userSecurityUserAuthIp 2 }
			  
			userSecurityUserAuthIpAccessTelnet OBJECT-TYPE
              SYNTAX  INTEGER{
	      		disable(0), 					
	      		enable(1)					
	      		}
              MAX-ACCESS  read-write
              STATUS  current
              DESCRIPTION
                      "0. disable -- Telnet frame sent to the switch will be dropped
					  1. enable -- Telnet frame whose source ip is auth ip sent to the switch will be accepted"
              ::= { userSecurityUserAuthIp 3 }
			  
			userSecurityUserAuthIpAccessSsh OBJECT-TYPE
              SYNTAX  INTEGER{
	      		disable(0), 					
	      		enable(1)					
	      		}
              MAX-ACCESS  read-write
              STATUS  current
              DESCRIPTION
                      "0. disable -- SSH frame sent to the switch will be dropped
					  1. enable -- SSH frame whose source ip is auth ip sent to the switch will be accepted"
              ::= { userSecurityUserAuthIp 4 }
			  
			userSecurityUserAuthIpAccessHttp OBJECT-TYPE
              SYNTAX  INTEGER{
	      		disable(0), 					
	      		enable(1)					
	      		}
              MAX-ACCESS  read-write
              STATUS  current
              DESCRIPTION
                      "0. disable -- HTTP frame sent to the switch will be dropped
					  1. enable -- HTTP frame whose source ip is auth ip sent to the switch will be accepted"
              ::= { userSecurityUserAuthIp 5 }
			  
			userSecurityUserAuthIpAccessHttps OBJECT-TYPE
              SYNTAX  INTEGER{
	      		disable(0), 					
	      		enable(1)					
	      		}
              MAX-ACCESS  read-write
              STATUS  current
              DESCRIPTION
                      "0. disable -- HTTPS frame sent to the switch will be dropped
					  1. enable -- HTTPS frame whose source ip is auth ip sent to the switch will be accepted"
              ::= { userSecurityUserAuthIp 6 }
			  
			userSecurityUserAuthIpAccessPing OBJECT-TYPE
              SYNTAX  INTEGER{
	      		disable(0), 					
	      		enable(1)					
	      		}
              MAX-ACCESS  read-write
              STATUS  current
              DESCRIPTION
                      "0. disable -- Ping request frame sent to the switch through be dropped
					  1. enable -- Ping request frame whose source ip is auth ip sent to the switch will be accepted"
              ::= { userSecurityUserAuthIp 7 }
			  
			userSecurityUserAuthIpAddress OBJECT-TYPE
              SYNTAX  IpAddress
              MAX-ACCESS  read-write
              STATUS  current
              DESCRIPTION
                      "the IPAddress that can visit the switch ,you can set or get its IPAddress via the interface.for example: 192.168.0.1"
              ::= { userSecurityUserAuthIp 8 }
              
          userSecurityUserAuthIpMask OBJECT-TYPE
              SYNTAX  IpAddress
              MAX-ACCESS  read-write
              STATUS  current
              DESCRIPTION
                      "the ipMask of the switch.for example: 192.168.0.1"
              ::= { userSecurityUserAuthIp 9 }
          
          --MAC
         userSecurityUserAuthMac  OBJECT IDENTIFIER ::= { userSecurityUserAuth 4 }
              
          userSecurityUserAuthMacEnable OBJECT-TYPE
              SYNTAX  INTEGER{
	      		disable(0), 					
	      		enable(1)					
	      		}
              MAX-ACCESS  read-write
              STATUS  current
              DESCRIPTION
                       "0. disable
                      1.enable"
              ::= { userSecurityUserAuthMac 1 }
		  
		  userSecurityUserAuthMacAccessSnmp OBJECT-TYPE
              SYNTAX  INTEGER{
	      		disable(0), 					
	      		enable(1)					
	      		}
              MAX-ACCESS  read-write
              STATUS  current
              DESCRIPTION
                      "0. disable -- SNMP frame sent to the switch will be dropped
					  1. enable -- SNMP frame whose source mac is auth mac sent to the switch through the port will be accepted"
              ::= { userSecurityUserAuthMac 2 }
			  
			userSecurityUserAuthMacAccessTelnet OBJECT-TYPE
              SYNTAX  INTEGER{
	      		disable(0), 					
	      		enable(1)					
	      		}
              MAX-ACCESS  read-write
              STATUS  current
              DESCRIPTION
                      "0. disable -- Telnet frame sent to the switch will be dropped
					  1. enable -- Telnet frame whose source mac is auth mac sent to the switch will be accepted"
              ::= { userSecurityUserAuthMac 3 }
			  
			userSecurityUserAuthMacAccessSsh OBJECT-TYPE
              SYNTAX  INTEGER{
	      		disable(0), 					
	      		enable(1)					
	      		}
              MAX-ACCESS  read-write
              STATUS  current
              DESCRIPTION
                      "0. disable -- SSH frame sent to the switch will be dropped
					  1. enable -- SSH frame whose source mac is auth mac sent to the switch through the port will be accepted"
              ::= { userSecurityUserAuthMac 4 }
			  
			userSecurityUserAuthMacAccessHttp OBJECT-TYPE
              SYNTAX  INTEGER{
	      		disable(0), 					
	      		enable(1)					
	      		}
              MAX-ACCESS  read-write
              STATUS  current
              DESCRIPTION
                      "0. disable -- HTTP frame sent to the switch will be dropped
					  1. enable -- HTTP frame whose source mac is auth mac sent to the switch through the port will be accepted"
              ::= { userSecurityUserAuthMac 5 }
			  
			userSecurityUserAuthMacAccessHttps OBJECT-TYPE
              SYNTAX  INTEGER{
	      		disable(0), 					
	      		enable(1)					
	      		}
              MAX-ACCESS  read-write
              STATUS  current
              DESCRIPTION
                      "0. disable -- HTTPS frame sent to the switch will be dropped
					  1. enable -- HTTPS frame whose source mac is auth mac sent to the switch through the port will be accepted"
              ::= { userSecurityUserAuthMac 6 }
			  
			userSecurityUserAuthMacAccessPing OBJECT-TYPE
              SYNTAX  INTEGER{
	      		disable(0), 					
	      		enable(1)					
	      		}
              MAX-ACCESS  read-write
              STATUS  current
              DESCRIPTION
                      "0. disable -- Ping request frame sent to the switch will be dropped
					  1. enable -- Ping request frame whose source mac is auth mac sent to the switch through the port will be accepted"
              ::= { userSecurityUserAuthMac 7 }
              
          userSecurityUserAuthMacAddress OBJECT-TYPE
              SYNTAX  OCTET STRING (SIZE (0..255))
              MAX-ACCESS  read-write
              STATUS  current
              DESCRIPTION
                      "the mac"
              ::= { userSecurityUserAuthMac 8 }
				
			
          
            
          END
