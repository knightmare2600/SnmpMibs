TPLINK-DHCPRELAY-MIB DEFINITIONS ::= BEGIN
       
       IMPORTS
         	TPRowStatus
						FROM TPLINK-TC-MIB
			MODULE-IDENTITY, OBJECT-TYPE, IpAddress
          	  	        FROM SNMPv2-SMI
          	tplinkMgmt
						FROM TPLINK-MIB
			ifIndex
						FROM RFC1213-MIB;
						
			tplinkDhcpRelayMIB MODULE-IDENTITY
				LAST-UPDATED    "201212171121Z"
				ORGANIZATION    "TPLINK"
				CONTACT-INFO    "www.tplink.com.cn"
				DESCRIPTION	    "Private MIB for DHCP Relay configuration."
				REVISION        "201212171121Z"
				DESCRIPTION
				"Initial version of this MIB module."
			::= { tplinkMgmt 39 }
		
			tplinkDhcpRelayMIBObjects			OBJECT IDENTIFIER	::= { tplinkDhcpRelayMIB 1 }
			tplinkDhcpRelayNotifications		OBJECT IDENTIFIER	::= { tplinkDhcpRelayMIB 2 }
			
			dhcpRelayGlobalConfig		OBJECT IDENTIFIER ::= {tplinkDhcpRelayMIBObjects 1}
			dhcpRelayServerConfig		OBJECT IDENTIFIER ::= {tplinkDhcpRelayMIBObjects 2}			  
			
			dhcpRelayOption82Support OBJECT-TYPE
            	SYNTAX  INTEGER{
	      			disable(0), 						--disable
	      			enable(1)								--enable
	      		}
            	MAX-ACCESS  read-write
            	STATUS  current
            	DESCRIPTION
                      "Enable or disable DHCP relay option 82 support on the switch."
            ::= { dhcpRelayGlobalConfig 1 }
			  
			dhcpRelayExistedOption82Field OBJECT-TYPE
            	SYNTAX  INTEGER{
	      			keep(0), 						--keep
	      			replace(1),						--replace
					drop(2)							--drop
	      		}
            	MAX-ACCESS  read-write
            	STATUS  current
            	DESCRIPTION
                      "Select how to handle existed DHCP relay option 82 field."
            ::= { dhcpRelayGlobalConfig 2 }
			  
			dhcpRelayOption82Customization OBJECT-TYPE
            	SYNTAX  INTEGER{
	      			disable(0), 						--disable
	      			enable(1)							--enable
	      		}
            	MAX-ACCESS  read-write
            	STATUS  current
            	DESCRIPTION
                      "Select Enable/Disable DHCP relay option 82 customization on the switch."
            ::= { dhcpRelayGlobalConfig 3 }
			  
			dhcpRelayOption82CircuitID OBJECT-TYPE
            	SYNTAX  OCTET STRING (SIZE (0..63)) 
            	MAX-ACCESS  read-write
            	STATUS  current
            	DESCRIPTION
                      "Specify the Option 82 customized Circuit ID.(1-63 characters)"
            ::= { dhcpRelayGlobalConfig 4 }
			  
			dhcpRelayOption82RemoteID OBJECT-TYPE
            	SYNTAX  OCTET STRING (SIZE (0..63)) 
            	MAX-ACCESS  read-write
            	STATUS  current
            	DESCRIPTION
                      "Specify the Option 82 customized Remote ID.(1-63 characters)"
            ::= { dhcpRelayGlobalConfig 5 }

        
		--**************
		--Set VLAN Interface	
		--**************
        dhcpRelayServerVlanInterfaceTable OBJECT-TYPE
			SYNTAX SEQUENCE OF DhcpRelayServerVlanInterfaceEntry
			MAX-ACCESS not-accessible
			STATUS current
			DESCRIPTION
						"The list of DHCP server of VLAN interface."
			::= {dhcpRelayServerConfig 1}
			
		dhcpRelayServerVlanInterfaceEntry OBJECT-TYPE
			SYNTAX  DhcpRelayServerVlanInterfaceEntry
			MAX-ACCESS  not-accessible
			STATUS  current
			DESCRIPTION
                    "DHCP server entries."
			INDEX   {dhcpRelayServerVlanId,
						dhcpRelayServerVlanInterfaceIp}
			::= { dhcpRelayServerVlanInterfaceTable 1 }
			
		DhcpRelayServerVlanInterfaceEntry ::=
            SEQUENCE {
            		dhcpRelayServerVlanId
            			INTEGER,
					dhcpRelayServerVlanInterfaceIp
						IpAddress, 
					dhcpRelayServerVlanInterfaceStatus
						TPRowStatus
            }
            
        dhcpRelayServerVlanId OBJECT-TYPE
            SYNTAX  INTEGER
            MAX-ACCESS  read-only
            STATUS  current
            DESCRIPTION
                      "VLAN interface ID."
              ::= { dhcpRelayServerVlanInterfaceEntry 1 }
			
		dhcpRelayServerVlanInterfaceIp OBJECT-TYPE
            SYNTAX  IpAddress
            MAX-ACCESS  read-only
            STATUS  current
            DESCRIPTION
                      "DHCP Server IP address."
              ::= { dhcpRelayServerVlanInterfaceEntry 2 }
			  			  
		dhcpRelayServerVlanInterfaceStatus OBJECT-TYPE
            SYNTAX  TPRowStatus
            MAX-ACCESS  read-create
            STATUS  current
            DESCRIPTION
                     " The following values are states:
                     these values may be used as follow:
                     active(1),if the entry is being used.
                     createAndGo(4),not being used.
                     destroy(6),destory the entry."
         	::={ dhcpRelayServerVlanInterfaceEntry 3 }
			
		--**************
		--Set Loopback Interface	
		--**************
		dhcpRelayServerLoopbackInterfaceTable OBJECT-TYPE
			SYNTAX SEQUENCE OF DhcpRelayServerLoopbackInterfaceEntry
			MAX-ACCESS not-accessible
			STATUS current
			DESCRIPTION
						"The list of DHCP server of loopback interface."
			::= {dhcpRelayServerConfig 2}
			
		dhcpRelayServerLoopbackInterfaceEntry OBJECT-TYPE
			SYNTAX  DhcpRelayServerLoopbackInterfaceEntry
			MAX-ACCESS  not-accessible
			STATUS  current
			DESCRIPTION
                    "DHCP server entries."
			INDEX   {dhcpRelayServerLoopbackId,
						dhcpRelayServerLoopbackInterfaceIp}
			::= { dhcpRelayServerLoopbackInterfaceTable 1 }
			
		DhcpRelayServerLoopbackInterfaceEntry ::=
            SEQUENCE {
            		dhcpRelayServerLoopbackId
            			INTEGER,
					dhcpRelayServerLoopbackInterfaceIp
						IpAddress, 
					dhcpRelayServerLoopbackInterfaceStatus
						TPRowStatus
            }
            
        dhcpRelayServerLoopbackId OBJECT-TYPE
            SYNTAX  INTEGER
            MAX-ACCESS  read-only
            STATUS  current
            DESCRIPTION
                      "Loopback interface ID (1-2147483647)."
              ::= { dhcpRelayServerLoopbackInterfaceEntry 1 }
			
		dhcpRelayServerLoopbackInterfaceIp OBJECT-TYPE
            SYNTAX  IpAddress
            MAX-ACCESS  read-only
            STATUS  current
            DESCRIPTION
                      "DHCP Server IP address."
              ::= { dhcpRelayServerLoopbackInterfaceEntry 2 }
			  			  
		dhcpRelayServerLoopbackInterfaceStatus OBJECT-TYPE
            SYNTAX  TPRowStatus
            MAX-ACCESS  read-create
            STATUS  current
            DESCRIPTION
                     " The following values are states:
                     these values may be used as follow:
                     active(1),if the entry is being used.
                     createAndGo(4),not being used.
                     destroy(6),destory the entry."
         	::={ dhcpRelayServerLoopbackInterfaceEntry 3 }
			
			
		--**************
		--Set routed port Interface	
		--**************
		dhcpRelayServerRoutedPortInterfaceTable OBJECT-TYPE
			SYNTAX SEQUENCE OF DhcpRelayServerRoutedPortInterfaceEntry
			MAX-ACCESS not-accessible
			STATUS current
			DESCRIPTION
						"The list of DHCP server of routed port interface."
			::= {dhcpRelayServerConfig 3}
			
		dhcpRelayServerRoutedPortInterfaceEntry OBJECT-TYPE
			SYNTAX  DhcpRelayServerRoutedPortInterfaceEntry
			MAX-ACCESS  not-accessible
			STATUS  current
			DESCRIPTION
                    "DHCP server entries."
			INDEX   {	ifIndex,
						dhcpRelayServerRoutedPortInterfaceIp}
			::= { dhcpRelayServerRoutedPortInterfaceTable 1 }
			
		DhcpRelayServerRoutedPortInterfaceEntry ::=
            SEQUENCE {
					dhcpRelayServerRoutedPortPortId
						OCTET STRING,
					dhcpRelayServerRoutedPortInterfaceIp
						IpAddress, 
					dhcpRelayServerRoutedPortInterfaceStatus
						TPRowStatus
            }
			
		dhcpRelayServerRoutedPortPortId OBJECT-TYPE
            SYNTAX  OCTET STRING (SIZE (0..16))
            MAX-ACCESS  read-only
            STATUS  current
            DESCRIPTION
                      "Displays the port ID."
              ::= { dhcpRelayServerRoutedPortInterfaceEntry 1 }
			
		dhcpRelayServerRoutedPortInterfaceIp OBJECT-TYPE
            SYNTAX  IpAddress
            MAX-ACCESS  read-only
            STATUS  current
            DESCRIPTION
                      "DHCP Server IP address."
              ::= { dhcpRelayServerRoutedPortInterfaceEntry 2 }
			  			  
		dhcpRelayServerRoutedPortInterfaceStatus OBJECT-TYPE
            SYNTAX  TPRowStatus
            MAX-ACCESS  read-create
            STATUS  current
            DESCRIPTION
                     " The following values are states:
                     these values may be used as follow:
                     active(1),if the entry is being used.
                     createAndGo(4),not being used.
                     destroy(6),destory the entry."
         	::={ dhcpRelayServerRoutedPortInterfaceEntry 3 }

	 END
